; ----------------------------------------------------------------------------------------------------------------------------------------------------------
; Problem	:	Each new term in the Fibonacci sequence is generated by adding the previous two terms. By starting with 1 and 2, the first 10 terms will be:
;				1, 2, 3, 5, 8, 13, 21, 34, 55, 89, ...
;				By considering the terms in the Fibonacci sequence whose values do not exceed four million, find the sum of the even-valued terms.
; Language	:	AutoLisp
; Date		:	22.06.2018
; written by:	J.E.Nolting
; ----------------------------------------------------------------------------------------------------------------------------------------------------------

(defun c:fibonacci_sequence_even_valued()
	(setq	x 1
			y 2
			sum 0)
	
	(while (< y 4000000)
		(if (= (rem y 2) 0)
			(progn
				(setq sum(+ sum y))
				(princ sum)(princ "\n")
			)
		)
		(setq 	z (+ x y)
				x y
				y z
		)
	)
	(princ (strcat "het antwoord is: " (itoa sum) "\n"))
	(princ)
)
